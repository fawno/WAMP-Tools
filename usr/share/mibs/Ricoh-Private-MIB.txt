RicohPrivateMIB DEFINITIONS ::= BEGIN

    IMPORTS
					 enterprises FROM RFC1155-SMI;

 -- Ricoh-Private-MIB

ricoh                    OBJECT IDENTIFIER ::= { enterprises 367 }
ricohAgentsID            OBJECT IDENTIFIER ::= { ricoh 1 1 }
ricohM109                OBJECT IDENTIFIER ::= { ricoh 1 2 1 1 6 16 }
ricohM103                OBJECT IDENTIFIER ::= { ricoh 1 2 1 1 6 23 }
ricohM105                OBJECT IDENTIFIER ::= { ricoh 1 2 1 1 6 29 }
ricohM120                OBJECT IDENTIFIER ::= { ricoh 1 2 1 1 6 85 }
ricohM112                OBJECT IDENTIFIER ::= { ricoh 1 2 1 1 6 91 }
ricohM139                OBJECT IDENTIFIER ::= { ricoh 1 2 1 1 6 178 }
ricohM147                OBJECT IDENTIFIER ::= { ricoh 1 2 1 1 6 200 }
ricohM048                OBJECT IDENTIFIER ::= { ricoh 1 2 1 1 6 201 }
ricohM048                OBJECT IDENTIFIER ::= { ricoh 1 2 1 1 6 202 }
ricohM148                OBJECT IDENTIFIER ::= { ricoh 1 2 1 1 6 203 }
ricohM153                OBJECT IDENTIFIER ::= { ricoh 1 2 1 1 6 209 }
ricohM153                OBJECT IDENTIFIER ::= { ricoh 1 2 1 1 6 210 }
ricohSys                 OBJECT IDENTIFIER ::= { ricoh 3 2 1 1 }
ricohSysDescr            OBJECT IDENTIFIER ::= { ricohSys 1 }
ricohEng                 OBJECT IDENTIFIER ::= { ricoh 3 2 1 2 }
ricohEngDescr            OBJECT IDENTIFIER ::= { ricohEng 1 }
ricohEngStatus           OBJECT IDENTIFIER ::= { ricohEng 2 }
ricohEngEmulator         OBJECT IDENTIFIER ::= { ricohEng 6 }
--ricohEngEmulatorRPCS     OBJECT IDENTIFIER ::= { ricohEng 6 12 }
--ricohEngEmulatorPCL      OBJECT IDENTIFIER ::= { ricohEng 6 13 }
ricohEngOption           OBJECT IDENTIFIER ::= { ricohEng 11 }
ricohEngSearch           OBJECT IDENTIFIER ::= { ricohEng 13 }
ricohEngAdf              OBJECT IDENTIFIER ::= { ricohEng 15 }
ricohEngScan             OBJECT IDENTIFIER ::= { ricohEng 16 }
ricohEngEnergy           OBJECT IDENTIFIER ::= { ricohEng 17 }
ricohEngCounter          OBJECT IDENTIFIER ::= { ricohEng 19 }
--ricohEngCounterTable     OBJECT IDENTIFIER ::= { ricohEngCounter 5 }
--ricohEngCounterEntry     OBJECT IDENTIFIER ::= { ricohEngCounterTable 1 }
--ricohEngCounterIndex     OBJECT IDENTIFIER ::= { ricohEngCounterEntry 1 }
--ricohEngCounterType      OBJECT IDENTIFIER ::= { ricohEngCounterEntry 2 }
--ricohEngCounterIncrement OBJECT IDENTIFIER ::= { ricohEngCounterEntry 3 }
--ricohEngCounterUnit      OBJECT IDENTIFIER ::= { ricohEngCounterEntry 4 }
--ricohEngCounterName      OBJECT IDENTIFIER ::= { ricohEngCounterEntry 5 }
--ricohEngCounterDescr     OBJECT IDENTIFIER ::= { ricohEngCounterEntry 6 }
--ricohEngCounterRangeMax  OBJECT IDENTIFIER ::= { ricohEngCounterEntry 7 }
--ricohEngCounterRangeMin  OBJECT IDENTIFIER ::= { ricohEngCounterEntry 8 }
--ricohEngCounterValue     OBJECT IDENTIFIER ::= { ricohEngCounterEntry 9 }
ricohEngMFP              OBJECT IDENTIFIER ::= { ricohEng 20 }
ricohEngMFPGeneral       OBJECT IDENTIFIER ::= { ricohEngMFP 1 }
ricohEngMFPInput         OBJECT IDENTIFIER ::= { ricohEngMFP 2 }
ricohEngMFPOutput        OBJECT IDENTIFIER ::= { ricohEngMFP 3 }
ricohEngMFPInserter      OBJECT IDENTIFIER ::= { ricohEngMFP 5 }
ricohEngPrt              OBJECT IDENTIFIER ::= { ricohEng 21 }
ricohEngPrtGeneral       OBJECT IDENTIFIER ::= { ricohEngPrt 1 }
ricohEngPrtInput         OBJECT IDENTIFIER ::= { ricohEngPrt 2 }
ricohEngPrtOutput        OBJECT IDENTIFIER ::= { ricohEngPrt 3 }
ricohEngPrtAlert         OBJECT IDENTIFIER ::= { ricohEngPrt 4 }
ricohEnfPrtInserter      OBJECT IDENTIFIER ::= { ricohEngPrt 5 }
ricohEngFAX              OBJECT IDENTIFIER ::= { ricohEng 22 }
ricohEngFAXGeneral       OBJECT IDENTIFIER ::= { ricohEngFAX 1 }
ricohEngFAXInput         OBJECT IDENTIFIER ::= { ricohEngFAX 2 }
ricohEngFAXOutput        OBJECT IDENTIFIER ::= { ricohEngFAX 3 }
ricohEngFAXAlert         OBJECT IDENTIFIER ::= { ricohEngFAX 4 }
ricohEngFAXMemory        OBJECT IDENTIFIER ::= { ricohEngFAX 10 }
ricohEngFAXChannel       OBJECT IDENTIFIER ::= { ricohEngFAX 11 }
ricohEngFAXSendImage     OBJECT IDENTIFIER ::= { ricohEngFAX 12 }
ricohEngFAXAddress       OBJECT IDENTIFIER ::= { ricohEngFAX 13 }
ricohEngCpy              OBJECT IDENTIFIER ::= { ricohEng 23 }
ricohEngCpyGeneral       OBJECT IDENTIFIER ::= { ricohEngCpy 1 }
ricohEngCpyInput         OBJECT IDENTIFIER ::= { ricohEngCpy 2 }
ricohEngCpyOutput        OBJECT IDENTIFIER ::= { ricohEngCpy 3 }
ricohEngCpyAlert         OBJECT IDENTIFIER ::= { ricohEngCpy 4 }
ricohEngToner            OBJECT IDENTIFIER ::= { ricohEng 24 }
ricohEngURL              OBJECT IDENTIFIER ::= { ricohEng 25 }
ricohEngLocalStorage     OBJECT IDENTIFIER ::= { ricohEng 27 }
ricohQueJobPrt           OBJECT IDENTIFIER ::= { ricoh 3 2 1 3 2 1 }
ricohNetCont             OBJECT IDENTIFIER ::= { ricoh 3 2 1 6 }
ricohNetIf               OBJECT IDENTIFIER ::= { ricoh 3 2 1 7 }
ricohNetIfProperty       OBJECT IDENTIFIER ::= { ricohNetIf 1 }
ricohNetIp               OBJECT IDENTIFIER ::= { ricohNetIf 2 1 }
ricohNetAtk              OBJECT IDENTIFIER ::= { ricohNetIf 2 2 }
ricohNetNw               OBJECT IDENTIFIER ::= { ricohNetIf 2 3 }
ricohNetMsn              OBJECT IDENTIFIER ::= { ricohNetIf 2 4 }
ricohNetIfSrv            OBJECT IDENTIFIER ::= { ricohNetIf 3 }
ricohNetIfSrvSnmp        OBJECT IDENTIFIER ::= { ricohNetIfSrv 1 }
ricohNetIfSrvUrl         OBJECT IDENTIFIER ::= { ricohNetIfSrv 2 }
ricohNetIfSrvWINS        OBJECT IDENTIFIER ::= { ricohNetIfSrv 4 }

ricohSysName         OBJECT-TYPE
										 SYNTAX	Displaystring
										 ACCESS	read-only
										 STATUS	mandatory
										 DESCRIPTION	"System name in English."
										 ::= { ricohSysDescr 1 0 }

ricohSysVers         OBJECT-TYPE
										 SYNTAX	Displaystring
										 ACCESS	read-only
										 STATUS	mandatory
										 DESCRIPTION	"Version (string) of the controller system software."
										 ::= { ricohSysDescr 2 0 }

ricohSysContact      OBJECT-TYPE
										 SYNTAX	Displaystring
										 ACCESS	read-only
										 STATUS	mandatory
										 DESCRIPTION	"Name and contact information for the system administrator. No effect on the printer's state."
										 ::= { ricohSysDescr 3 0 }

ricohSysLocation     OBJECT-TYPE
										 SYNTAX	Displaystring
										 ACCESS	read-only
										 STATUS	mandatory
										 DESCRIPTION	"Describes the location of the system."
										 ::= { ricohSysDescr 4 0 }

ricohSysProductID    OBJECT-TYPE
										 SYNTAX OBJECT IDENTIFIER
										 ACCESS	read-only
										 STATUS	mandatory
										 DESCRIPTION	"Product identifier that refers to this system."
										 ::= { ricohSysDescr 5 0 }

riochSysOemID        OBJECT-TYPE
										 SYNTAX OCTET STRING
										 ACCESS	read-only
										 STATUS	mandatory
										 DESCRIPTION	"Vendor name to identify OEM."
										 ::= { ricohSysDescr 7 0 }

ricohSysLanguage     OBJECT-TYPE
										 SYNTAX OCTET STRING
										 ACCESS	read-only
										 STATUS	mandatory
										 DESCRIPTION	"Language setting for the panel display."
										 ::= { ricohSysDescr 8 0 }

ricohSysCountry      OBJECT-TYPE
										 SYNTAX OCTET STRING
										 ACCESS	read-only
										 STATUS	mandatory
										 DESCRIPTION	"Returns the value of the language set for the panel display."
										 ::= { ricohSysDescr 9 0 }

ricohSysMIBVersion   OBJECT-TYPE
										 SYNTAX OCTET STRING
										 ACCESS	read-only
										 STATUS	mandatory
										 DESCRIPTION	"Version code (string) of supported RicohPrivateMIB. (Format: 'YYMMDDhhmmT')"
										 ::= { ricohSysDescr 10 0 }

ricohSysDeviceID     OBJECT-TYPE
										 SYNTAX OCTET STRING
										 ACCESS	read-only
										 STATUS	mandatory
										 DESCRIPTION	"ID represented by string which is equivalent of IEEE1284 DeviceIDString."
										 ::= { ricohSysDescr 11 0 }

ricohEngSerialNumber OBJECT-TYPE
										 SYNTAX OCTET STRING
										 ACCESS	read-only
										 STATUS	mandatory
										 DESCRIPTION	"Serial number (string) of the plotter engine."
										 ::= { ricohEngDescr 4 0 }

ricohEngScanStatShare OBJECT-TYPE
										 SYNTAX INTEGER { shareAble(1), notShareAble(2) }
										 ACCESS	read-only
										 STATUS	mandatory
										 DESCRIPTION
																	"Scanner status.
																	[GET]:
																	shareAble(1): Scanner available for sharing,
																	notShareAble(2): Scanner unavailable for sharing"
										 ::= { ricohEngStatus 11 0 }

ricohEngScanStatContactGlass OBJECT-TYPE
										 SYNTAX INTEGER { unknown(0), paperExist(1), notPaperExist(2) }
										 ACCESS	read-only
										 STATUS	mandatory
										 DESCRIPTION
																	"Status of paper on contact glass.
																	[GET]:
																	unknown(0): Unknown,
																	paperExist(1): There is paper remaining,
																	notPaperExist(2): Out of paper"
										 ::= { ricohEngStatus 12 0 }

ricohEngScanStatError OBJECT-TYPE
										 SYNTAX INTEGER { noError(0), feedError(2), hardwareError(3), servicemanCall(4) }
										 ACCESS	read-only
										 STATUS	mandatory
										 DESCRIPTION
																	"Error status
																	[GET]:
																	noError(0): No error,
																	feedError(2): ADF error (Jam),
																	hardwareError(3): Hardware error (never occurs),
																	servicemanCall(4): Service Call"
										 ::= { ricohEngStatus 13 0 }

ricohEngScanStatFunctionCurrent    OBJECT-TYPE
							              			 SYNTAX INTEGER
              										 ACCESS	read-only
							              			 STATUS	mandatory
              										 DESCRIPTION	"Feature in use.
              										               [GET]:
              										               Set when a scanning application is using the current scanner resource.
                            										 The bit is not set when something other than the scanning application (e.g., copier) is using it.
                            										 Bit0:Undefinedfunction: Undefined feature,
                            										 Bit1:Distributionscanner: Distribution scanner,
                            										 Bit2:Remotescanner: Remote TWAIN scanner,
                            										 Bit3-31:Reserved: Reserved bits"
              										 ::= { ricohEngStatus 14 0 }

ricohEngScanStatUserCurrent        OBJECT-TYPE
              										 SYNTAX STRING
              										 ACCESS	read-only
              										 STATUS	mandatory
              										 DESCRIPTION	"User identification
              										               [GET]:
              										               Remote: IP address of the connected host,
              										               Under distribution: Unused"
              										 ::= { ricohEngStatus 15 0 }

ricohEngScanStatCompressBiLevel    OBJECT-TYPE
              										 SYNTAX INTEGER
              										 ACCESS	read-only
              										 STATUS	mandatory
              										 DESCRIPTION	"Bi-level compression.
              										               [GET]:
              										               Instance of ricohEngScanCompressionType."
							              			 ::= { ricohEngStatus 16 0 }

ricohEngScanStatCompressMultiLevel OBJECT-TYPE
										               SYNTAX INTEGER
										               ACCESS	read-only
										               STATUS	mandatory
              										 DESCRIPTION	"Multi-level compression.
              										               [GET]:
              										               Instance of ricohEngScanCompressionType."
              										 ::= { ricohEngStatus 17 0 }

ricohEngScanStatSummary            OBJECT-TYPE
										               SYNTAX INTEGER
										               ACCESS	read-only
										               STATUS	mandatory
              										 DESCRIPTION	"Summary error status of scanning application.
              										               [GET]:
              										               Bit0:errorPaperOnContactGlass: Paper on contact glass,
              										               Bit1:errorADFLiftUp: ADF lifted up,
              										               Bit2:errorADFJam: ADF jam,
              										               Bit3:errorADFCoverOpen: ADF cover is open,
              										               Bit4:errorOther: Other errors,
              										               Bit5:errorUserMaintenance: User maintenance,
              										               Bit6:servicemanCall: Service call,
              										               Bit7:powerOff: Power OFF,
              										               Bit8:alertOccupied: In use,
              										               Bit9:alertOther: Other warning,
              										               Bit10-31:Reserved(Mustbe0): Reserved bits"
              										 ::= { ricohEngStatus 18 0 }

ricohEngEmulatorRPCSTable OBJECT-TYPE
    SYNTAX      SEQUENCE OF ricohEngEmulatorRPCSEntry
    MAX-ACCESS  not-accessible
    STATUS      current
    DESCRIPTION
        ""
    ::= { ricohEng 6 12 }

ricohEngEmulatorRPCSEntry OBJECT-TYPE
    SYNTAX      RicohEngEmulatorRPCSEntry
    MAX-ACCESS  not-accessible
    STATUS      current
    DESCRIPTION
        ""
    INDEX       { ricohEngEmulatorRPCSIndex }
    ::= { ricohEngEmulatorRPCSTable 1 }

RicohEngEmulatorRPCSEntry ::= SEQUENCE {
    ricohEngEmulatorRPCSIndex             Integer32,
    ricohEngEmulatorRPCSData              OCTET STRING
}

ricohEngEmulatorRPCSIndex OBJECT-TYPE
   SYNTAX      Integer32
   MAX-ACCESS  not-accessible
   STATUS      current
   DESCRIPTION ""
   ::= { ricohEngEmulatorRPCSEntry 1 1 }

ricohEngEmulatorRPCSData OBJECT-TYPE
   SYNTAX      OCTET STRING
   MAX-ACCESS  not-accessible
   STATUS      current
   DESCRIPTION ""
   ::= { ricohEngEmulatorRPCSEntry 2 1 }

ricohEngEmulatorPCLTable OBJECT-TYPE
    SYNTAX      SEQUENCE OF ricohEngEmulatorPCLEntry
    MAX-ACCESS  not-accessible
    STATUS      current
    DESCRIPTION
        ""
    ::= { ricohEng 6 13 }

ricohEngEmulatorPCLEntry OBJECT-TYPE
    SYNTAX      RicohEngEmulatorPCLEntry
    MAX-ACCESS  not-accessible
    STATUS      current
    DESCRIPTION
        ""
    INDEX       { ricohEngEmulatorPCLIndex }
    ::= { ricohEngEmulatorPCLTable 1 }

RicohEngEmulatorPCLEntry ::= SEQUENCE {
    ricohEngEmulatorPCLIndex             Integer32,
    ricohEngEmulatorPCLData              OCTET STRING
}

ricohEngEmulatorPCLIndex OBJECT-TYPE
   SYNTAX      Integer32
   MAX-ACCESS  not-accessible
   STATUS      current
   DESCRIPTION ""
   ::= { ricohEngEmulatorPCLEntry 1 1 }

ricohEngEmulatorPCLData OBJECT-TYPE
   SYNTAX      OCTET STRING
   MAX-ACCESS  not-accessible
   STATUS      current
   DESCRIPTION ""
   ::= { ricohEngEmulatorPCLEntry 2 1 }

ricohEngOptionIdTable OBJECT-TYPE
    SYNTAX      SEQUENCE OF ricohEngOptionIdEntry
    MAX-ACCESS  not-accessible
    STATUS      current
    DESCRIPTION
        ""
    ::= { ricohEngOption 2 }

ricohEngOptionIdEntry OBJECT-TYPE
    SYNTAX      RicohEngOptionIdEntry
    MAX-ACCESS  not-accessible
    STATUS      current
    DESCRIPTION
        ""
    INDEX       { ricohEngOptionIdIndex }
    ::= { ricohEngOptionIdTable 1 }

RicohEngOptionIdEntry ::= SEQUENCE {
    ricohEngOptionIdIndex             Integer32,
    ricohEngOptionIdentifyNumber      Integer32
}

ricohEngOptionIdIndex OBJECT-TYPE
   SYNTAX      Integer32
   MAX-ACCESS  not-accessible
   STATUS      current
   DESCRIPTION ""
   ::= { ricohEngOptionIdEntry 1 }

ricohEngOptionIdentifyNumber OBJECT-TYPE
   SYNTAX      Integer32
   MAX-ACCESS  not-accessible
   STATUS      current
   DESCRIPTION ""
   ::= { ricohEngOptionIdEntry 2 }

ricohEngOptionFuncTable OBJECT-TYPE
    SYNTAX      SEQUENCE OF ricohEngOptionFuncEntry
    MAX-ACCESS  not-accessible
    STATUS      current
    DESCRIPTION
        ""
    ::= { ricohEngOption 3 }

ricohEngOptionFuncEntry OBJECT-TYPE
    SYNTAX      RicohEngOptionFuncEntry
    MAX-ACCESS  not-accessible
    STATUS      current
    DESCRIPTION
        ""
    INDEX       { ricohEngOptionFuncIndex }
    ::= { ricohEngOptionFuncTable 1 }

RicohEngOptionFuncEntry ::= SEQUENCE {
    ricohEngOptionFuncIndex             Integer32,
    ricohEngOptionFuncType      				Integer32
}

ricohEngOptionFuncIndex OBJECT-TYPE
   SYNTAX      Integer32
   MAX-ACCESS  not-accessible
   STATUS      current
   DESCRIPTION ""
   ::= { ricohEngOptionFuncEntry 1 }

ricohEngOptionFuncType OBJECT-TYPE
   SYNTAX      Integer32 { inputManual(1000), printDuplex(2000), printThickPaper(2001), printEsort(2002), printReplot(2003), printPasswdAtPanel(2004), printJobSpooler(2005), printHoldFile(2006), printStoredFile(2007), outputStaple(3003), outputPunch(3004), outputFolding(3005), outputDoggeyTail(3006), outputCenterStaple(3008), outputInserter(3009), panelLock(5006), documentBox(5007) }
   MAX-ACCESS  not-accessible
   STATUS      current
   DESCRIPTION ""
   ::= { ricohEngOptionFuncEntry 2 }

ricohEngSearchFunction OBJECT-TYPE
   SYNTAX      Integer32 -- BITS { Printer(0), Scanner(1), Fax(2), Copy(3), UsageRestriction(8), LocalStorage(9) }
   MAX-ACCESS  not-accessible
   STATUS      current
   DESCRIPTION ""
   ::= { ricohEngSearch 3 0 }

ricohEngAdfType OBJECT-TYPE
   SYNTAX      INTEGER { none(1), singleSide(2), bothSide(3), ardf(4), page(5) }
   MAX-ACCESS  not-accessible
   STATUS      current
   DESCRIPTION ""
   ::= { ricohEngAdf 1 0 }

ricohEngAdfName OBJECT-TYPE
   SYNTAX      OCTET STRING
   MAX-ACCESS  not-accessible
   STATUS      current
   DESCRIPTION ""
   ::= { ricohEngAdf 2 0 }

ricohEngAdfMultiSizePaper OBJECT-TYPE
   SYNTAX      PropertySwitch { off(0) }
   MAX-ACCESS  not-accessible
   STATUS      current
   DESCRIPTION ""
   ::= { ricohEngAdf 3 0 }

ricohEngScanColorType OBJECT-TYPE
   SYNTAX      INTEGER { blackAndWhite(1), color(2) }
   ACCESS      read-only
   STATUS      current
   DESCRIPTION ""
   ::= { ricohEngScan 1 0 }

ricohEngScanColorDepthTable OBJECT-TYPE
    SYNTAX      SEQUENCE OF ricohEngOptionFuncEntry
    MAX-ACCESS  not-accessible
    STATUS      current
    DESCRIPTION
        ""
    ::= { ricohEngScan 2 }

ricohEngScanColorDepthEntry OBJECT-TYPE
    SYNTAX      RicohEngScanColorDepthEntry
    MAX-ACCESS  not-accessible
    STATUS      current
    DESCRIPTION
        ""
    INDEX       { ricohEngScanColorDepthIndex }
    ::= { ricohEngScanColorDepthTable 1 }

RicohEngScanColorDepthEntry ::= SEQUENCE {
    ricohEngScanColorDepthIndex             Integer32,
    ricohEngScanColorDepthType      				Integer32
}

ricohEngScanColorDepthIndex OBJECT-TYPE
   SYNTAX      Integer32
   MAX-ACCESS  not-accessible
   STATUS      current
   DESCRIPTION ""
   ::= { ricohEngScanColorDepthEntry 1 }

ricohEngScanColorDepthType OBJECT-TYPE
   SYNTAX      Integer32 { unknown(0), biLevelColor(1), biLevelDitherHalfTone(2), biLevelDiffusion(3), depth16(4), depth256(5), depth4096(6), depth16384(7), depth65536(8), biLevelRGBColor(9), biLevelRGBDitherHalfTone(10), biLevelRGBDiffusion(11) }
   MAX-ACCESS  not-accessible
   STATUS      current
   DESCRIPTION ""
   ::= { ricohEngScanColorDepthEntry 2 }

ricohEngCounterTotal               OBJECT-TYPE
										               SYNTAX Integer32
										               ACCESS	read-only
										               STATUS	mandatory
              										 DESCRIPTION	"Total of all counters for the devices.
              										               [GET]:
              										               Total printed copies."
              										 ::= { ricohEngCounter 1 0 }

ricohEngCounterPrinter             OBJECT-TYPE
										               SYNTAX Integer32
										               ACCESS	read-only
										               STATUS	mandatory
              										 DESCRIPTION	"Counter for printer application.
                                                 [GET]:
                                                 Number of copies printed in printer mode."
              										 ::= { ricohEngCounter 2 0 }

ricohEngCounterFax                 OBJECT-TYPE
										               SYNTAX Integer32
										               ACCESS	read-only
										               STATUS	mandatory
              										 DESCRIPTION	"Counter for FAX application.
                                                 [GET]:
                                                 Number of copies printed in FAX mode. 0 for models with no FAX mode."
              										 ::= { ricohEngCounter 3 0 }

ricohEngCounterCopier              OBJECT-TYPE
										               SYNTAX Integer32
										               ACCESS	read-only
										               STATUS	mandatory
              										 DESCRIPTION	"Counter for copy application.
                                                 [GET]:
                                                 Number of copies in copy mode. 0 for models with no copy mode."
              										 ::= { ricohEngCounter 4 0 }

ricohEngCounterTable OBJECT-TYPE
    SYNTAX      SEQUENCE OF ricohCounterEntry
    MAX-ACCESS  not-accessible
    STATUS      current
    DESCRIPTION
        ""
    ::= { ricohEngCounter 5 }

ricohEngCounterEntry OBJECT-TYPE
    SYNTAX      RicohEngCounterEntry
    MAX-ACCESS  not-accessible
    STATUS      current
    DESCRIPTION
        ""
    INDEX       { ricohEngCounterIndex }
    ::= { ricohEngCounterTable 1 }


RicohEngCounterEntry ::= SEQUENCE {
    ricohEngCounterIndex             Integer32,
    ricohEngCounterType              Integer32,
    ricohEngCounterIncrement         Integer32,
    ricohEngCounterUnit              INTEGER,
    ricohEngCounterName              OCTET STRING,
    ricohEngCounterDescr             OCTET STRING,
    ricohEngCounterRangeMax          Integer32,
    ricohEngCounterRangeMin          Integer32,
    ricohEngCounterValue             Integer32
}

ricohEngCounterIndex OBJECT-TYPE
   SYNTAX      Integer32
   MAX-ACCESS  not-accessible
   STATUS      current
   DESCRIPTION ""
   ::= { ricohEngCounterEntry 1 }

ricohEngCounterType OBJECT-TYPE
   SYNTAX      Integer32 {
													 CounterMachineTotal(10),
													 CounterCopyTotal(200),
													 CounterCopyBlackWhite(201),
													 CounterCopySingleTwo-color(202),
													 CounterCopyFullColor(203),
													 CounterFAXTotal(300),
													 CounterFAXBlackWhite(301),
													 CounterPrintTotal(400),
													 CounterPrintBlackWhite(401),
													 CounterPrintSingleTwo-col(402),
													 CounterPrintFullColor(403),
													 TotalPrintsFullColor(600),
													 TotalPrintsMonocolor(601),
													 DevelopmentColor(602),
													 DevelopmentBlackWhite(603),
													 CopierColor(604),
													 CopierBlackWhite(605),
													 PrinterColor(606),
													 PrinterBlackWhite(607),
													 TotalPrintsColor(608),
													 TotalPrintsBlackWhite(609),
													 PrinterFullColor(612),
													 PrinterMonocolor(613),
													 TotalPrintsFullColor(614),
													 CopierBlackWhite(620),
													 CopierSingleColor(621),
													 CopierTwo-color(622),
													 CopierFullColor(623),
													 FaxBlackWhite(630),
													 FaxSingleColor(631),
													 PrinterBlackWhite(640),
													 Printer1or2ClrToner(641),
													 PrinterFullColor(642),
													 FromStorageBlackWhite(650),
													 FromStorageSingleColor(651),
													 FromStorageTwo-color(652),
													 FromStorageFullColor(653),
													 LargePaperPrints(700),
													 DuplexPrintedSides(701),
													 StaplesUsed(702)
													}
   MAX-ACCESS  not-accessible
   STATUS      current
   DESCRIPTION ""
   ::= { ricohEngCounterEntry 2 }


ricohEngCounterIncrement OBJECT-TYPE
   SYNTAX      Integer32
   MAX-ACCESS  not-accessible
   STATUS      current
   DESCRIPTION
			"0 unknown OFF(0),ON(1) (AlwaysOFF)
			1 other OFF(0),ON(1) (AlwaysOFF)
			2 Increment(0), decrement(1) Incremental or decremental counter
			3 PaperIn(0), PaperOut(1) When to count
			4 A3 DoubleCount ON(0),OFF(1) Whether to double count A3
			5 DLT DoubleCount ON(0),OFF(1) Whether to double count DLT
			6 Duplex DoubleCount ON(0),OFF(1) Whether to double count duplex printing
			7-31 Reserved as 0 (Always 0)"
   ::= { ricohEngCounterEntry 3 }

ricohEngCounterUnit OBJECT-TYPE
   SYNTAX      INTEGER
   MAX-ACCESS  not-accessible
   STATUS      current
   DESCRIPTION ""
   ::= { ricohEngCounterEntry 4 }

ricohEngCounterName OBJECT-TYPE
   SYNTAX      OCTET STRING
   MAX-ACCESS  not-accessible
   STATUS      current
   DESCRIPTION ""
   ::= { ricohEngCounterEntry 5 }

ricohEngCounterDescr OBJECT-TYPE
   SYNTAX      OCTET STRING
   MAX-ACCESS  not-accessible
   STATUS      current
   DESCRIPTION ""
   ::= { ricohEngCounterEntry 6 }

ricohEngCounterRangeMax OBJECT-TYPE
   SYNTAX      Integer32
   MAX-ACCESS  not-accessible
   STATUS      current
   DESCRIPTION ""
   ::= { ricohEngCounterEntry 7 }

ricohEngCounterRangeMin OBJECT-TYPE
   SYNTAX      Integer32
   MAX-ACCESS  not-accessible
   STATUS      current
   DESCRIPTION ""
   ::= { ricohEngCounterEntry 8 }

ricohEngCounterValue OBJECT-TYPE
   SYNTAX      Integer32
   MAX-ACCESS  not-accessible
   STATUS      current
   DESCRIPTION ""
   ::= { ricohEngCounterEntry 9 }

ricohEngMFPStatSummary             OBJECT-TYPE
										               SYNTAX INTEGER
										               ACCESS	read-only
										               STATUS	mandatory
              										 DESCRIPTION	"Summary error status of MFP(Platform).
              										               [GET]:
              										               Fixed to 0(ZERO)."
              										 ::= { ricohEngStatus 20 0 }

ricohEngFAXStatSummary             OBJECT-TYPE
										               SYNTAX INTEGER
										               ACCESS	read-only
										               STATUS	mandatory
              										 DESCRIPTION	"Summary error status of fax application.
              										               [GET]:
              										               Bit0:alertOther: 0x00000001,
              										               Bit1:alertTonerLow: 0x00000002,
              										               Bit2:alertOccupied: 0x00000004,
              										               Bit3:alertWarmUp: 0x00000008,
              										               Bit4:errorOther: 0x00000010,
              										               Bit5:errorScannerCoverOpen: 0x00000020,
              										               Bit6:errorPlotterCoverOpen: 0x00000040,
              										               Bit7:errorPaperEnd: 0x00000080,
              										               Bit8:errorScannerPaperJam: 0x00000100,
              										               Bit9:errorPlotterPaperJam: 0x00000200,
              										               Bit10:errorTonerEnd: 0x00000400,
              										               Bit11:errorFAXCommunication: 0x00000800,
              										               Bit12:errorMaintenance: 0x00001000,
              										               Bit13:servicemancall: 0x00002000,
              										               Bit14-31:Reserved(Must be 0)"
              										 ::= { ricohEngStatus 21 0 }

ricohEngCopyStatSummary            OBJECT-TYPE
										               SYNTAX INTEGER
										               ACCESS	read-only
										               STATUS	mandatory
              										 DESCRIPTION	"Summary error status.
              										               [GET]:
              										               Bit0:alertOther: 0x00000001,
              										               Bit1:alertTonerLow: 0x00000002,
              										               Bit2:alertOccupied: 0x00000004,
              										               Bit3:alertWarmUp: 0x00000008,
              										               Bit4:errorOther: 0x00000010,
              										               Bit5:errorScannerCoverOpen: 0x00000020,
              										               Bit6:errorPlotterCoverOpen: 0x00000040,
              										               Bit7:errorPaperEnd: 0x00000080,
              										               Bit8:errorScannerPaperJam: 0x00000100,
              										               Bit9:errorPlotterPaperJam: 0x00000200,
              										               Bit10:errorTonerEnd: 0x00000400,
              										               Bit11:servicemanCall: 0x00000800,
              										               Bit12:Reserved: (Must be 0)"
              										 ::= { ricohEngStatus 22 0 }



 -- definition of object types


END
